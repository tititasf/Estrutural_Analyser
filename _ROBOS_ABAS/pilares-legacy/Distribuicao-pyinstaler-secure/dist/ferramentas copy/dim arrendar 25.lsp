﻿(defun c:DimRoundUp (/ ent val newval textoverride)
  (setq ent (entlast)) ; Obtém o último objeto criado
  (if (and ent (= (cdr (assoc 0 (entget ent))) "DIMENSION")) ; Verifica se é uma dimensão
    (progn
      (setq val (cdr (assoc 42 (entget ent)))) ; Obtém o valor real da dimensão
      (setq val (+ (* val 2) 10)) ; Multiplica o valor por 2 e soma 10
      (setq newval (* 25 (/ (fix val) 25))) ; Calcula o arredondamento para baixo
      (setq textoverride (strcat "Perfil Metálico L=" (itoa newval))) ; Cria o texto final
      (vla-put-TextOverride (vlax-ename->vla-object ent) textoverride) ; Define o texto da dimensão
      (princ (strcat "\nTexto atualizado para: " textoverride)) ; Feedback no console
    )
    (princ "\nO último objeto não é uma dimensão ou é inválido.") ; Mensagem de erro se não for uma dimensão
  )
  (princ)
)
