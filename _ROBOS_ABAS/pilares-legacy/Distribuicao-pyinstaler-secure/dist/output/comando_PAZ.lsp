;; Comando para executar script SCR PAZ
(defun c:PAZ ()
  (command "_SCRIPT" "C:/Users/Ryzen/Desktop/Github2/pilares/pilares-atualizado-09-25/Distribuicao-pyinstaler-secure/dist/output/script_PAZ.scr")
  (princ)
)
