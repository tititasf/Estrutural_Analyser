;; Comando para executar script SCR PAZ
(defun c:PAZ ()
  (command "_SCRIPT" "C:/Users/Ryzen/Desktop/GITHUB/pilares/pilares-atualizado-09-25/Distribuicao-Final/dist/output/script_PAZ.scr")
  (princ)
)
