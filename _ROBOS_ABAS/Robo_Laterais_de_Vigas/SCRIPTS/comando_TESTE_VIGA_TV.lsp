;; Comando para executar script SCR automático (Gerado Dinamicamente)
(defun c:TV ()
  (command "_SCRIPT" "c:/Users/Ryzen/Desktop/GITHUB/Agente-cad-PYSIDE/_ROBOS_ABAS/Robo_Laterais_de_Vigas/SCRIPTS/TESTE_VIGA_TV.scr")
  (princ)
)
